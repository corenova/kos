module demo-blueprints {
  prefix demo;

  import kinetic-object-stream {
    prefix kos;
  }

  identity eth {
    base kos:protocol;
  }
  identity ipv4 {
    base kos:protocol;
  }
  identity gaps {
    base kos:protocol;
  }
  identity json {
    base gaps;
  }
  
  grouping coordinates {
    leaf lat {
      type decimal64 {
	fraction-digits 9;
      }
    }
    leaf lon {
      type decimal64 {
	fraction-digits 9;
      }
    }
    leaf alt {
      type decimal64 {
	fraction-digits 9;
      }
    }
  }
  grouping target-detection {
    leaf azimuth;
    leaf range;
  }

  kos:blueprint simple {
    kos:node Generator {
      kos:instanceof kos:generator;
      output {
	leaf data;
      }
    }
    kos:node Terminator {
      kos:instanceof kos:terminator;
      input {
	leaf data;
      }
    }
  }

  kos:blueprint pipeline {
    kos:node Generator {
      kos:instanceof kos:generator;
      output {
	leaf data;
      }
    }
    kos:node Processor {
      kos:instanceof kos:processor;
      input {
	leaf data;
      }
      output {
	leaf data;
      }
    }
    kos:node Terminator {
      kos:instanceof kos:terminator;
      input {
	leaf data;
      }
    }
  }

  kos:blueprint multi-io {
    kos:node Generator {
      kos:instanceof kos:generator;
      output {
	leaf data;
      }
    }
    kos:node Aggregator {
      kos:instanceof kos:processor;
      input {
	leaf data1;
	leaf data2;
	leaf data3;
      }
      output {
	leaf data1;
      }
    }
    kos:node Splitter {
      kos:instanceof kos:processor;
      input {
	leaf data1;
      }
      output {
	leaf data1;
	leaf data2;
	leaf data3;
      }
    }
    kos:node Terminator {
      kos:instanceof kos:terminator;
      input {
	leaf data;
      }
    }
  }

  kos:blueprint complex {
    kos:node GeneratorA {
      kos:instanceof kos:generator;
      output {
	leaf data;
      }
    }
    kos:node Splitter {
      kos:instanceof kos:processor;
      input {
	container object;
      }
      output {
	leaf data1;
	leaf data2;
	leaf data3;
      }
    }
    kos:node GeneratorB {
      kos:instanceof kos:generator;
      output {
	container object;
	leaf data;
      }
    }
    kos:node Aggregator {
      kos:instanceof kos:processor;
      input {
	leaf data1;
	leaf data2;
	leaf data3;
      }
      output {
	container object;
      }
    }
    kos:node Terminator {
      kos:instanceof kos:terminator;
      input {
	container object;
	leaf data1;
	leaf data2;
	leaf data3;
      }
    }
  }
  
  kos:blueprint positioning {
    kos:node pnt-sensor {
      kos:instanceof kos:generator;
      output {
	leaf lat {
	  type decimal64 {
	    fraction-digits 9;
	  }
	}
	leaf lon {
	  type decimal64 {
	    fraction-digits 9;
	  }
	}
	leaf alt {
	  type decimal64 {
	    fraction-digits 9;
	  }
	}
	leaf time;
      }
    }
    kos:node position-processor {
      kos:instanceof kos:processor;
      input {
	uses coordinates;
      }
      output {
	uses coordinates;
      }
    }
    kos:node ownship {
      kos:instanceof kos:processor;
      input {
	uses coordinates;
      }
      output {
	container global-fix {
	  uses coordinates;
	}
      }
    }
  }
  kos:blueprint calibrating {
    kos:node pnt-sensor {
      kos:instanceof kos:generator;
      output {
	leaf lat {
	  type decimal64 {
	    fraction-digits 9;
	  }
	}
	leaf lon {
	  type decimal64 {
	    fraction-digits 9;
	  }
	}
	leaf alt {
	  type decimal64 {
	    fraction-digits 9;
	  }
	}
      }
    }
    kos:node position-processor {
      kos:instanceof kos:processor;
      input {
	uses coordinates;
      }
      output {
	uses coordinates;
      }
    }
    kos:node ownship {
      kos:instanceof kos:processor;
      input {
	uses coordinates;
      }
      output {
	container global-fix {
	  uses coordinates;
	}
      }
    }
    kos:node altimeter {
      kos:instanceof kos:generator;
      output {
	leaf alt {
	  type decimal64 {
	    fraction-digits 9;
	  }
	}
      }
    }
  }
  kos:blueprint mission {
    kos:node pnt-sensor {
      kos:instanceof kos:generator;
      output {
	leaf lat {
	  type decimal64 {
	    fraction-digits 9;
	  }
	}
	leaf lon {
	  type decimal64 {
	    fraction-digits 9;
	  }
	}
	leaf alt {
	  type decimal64 {
	    fraction-digits 9;
	  }
	}
	leaf time;
      }
    }
    kos:node position-processor {
      kos:instanceof kos:processor;
      input {
	uses coordinates;
      }
      output {
	uses coordinates;
      }
    }
    kos:node ownship {
      kos:instanceof kos:processor;
      input {
	uses coordinates;
      }
      output {
	container global-fix {
	  uses coordinates;
	}
      }
    }
    kos:node rf-radar {
      kos:instanceof kos:generator;
      output {
	uses target-detection;
      }
    }
    kos:node time-processor {
      kos:instanceof kos:processor;
      input {
	leaf time;
      }
      output {
	leaf timestamp;
	leaf timetick;
      }
    }
    kos:node targeting {
      kos:instanceof kos:processor;
      input {
	container uav {
	  uses coordinates;
	}
	leaf timetick;
	container rf {
	  uses target-detection;
	}
      }
      output {
	container target-loc {
	  uses coordinates;
	}
      }
    }
  }
}
