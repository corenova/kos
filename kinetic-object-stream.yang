module kinetic-object-stream {
  namespace "urn:ietf:params:xml:ns:yang:kinetic-object-stream";
  prefix kos;

  organization
    "Corenova Technologies, Inc.";
  contact
    "Peter K. Lee <peter@corenova.com>";
  description
    "The core module of KOS which provides custom language extensions for
     defining personas, interfaces and components as well as modeling blueprints of nodes
     and flows.";

  revision 2020-04-17 {
    description
      "Updated to support additional extensions.";
  }
  revision 2018-03-10 {
    description
      "Initial revision.";
  }
  /*
   * Custom YANG Language Extensions
   */
  extension persona {
    argument "persona-name";
    description
      "defines a processing behavior that can be instantiated by an actor node";
  }
  extension component {
    argument "component-name";
    description
      "primary data processing model that instantiates a persona, extends other
      components, and implements other interfaces";
  }
  extension reaction {
    argument "reaction-function-name";
    description
      "A reactive function within a component that triggers based on one or more
      inputs and produces one or more outputs.";
  }
  extension implements {
    argument "target-interface-identifier";
    description
      "used by a component to implement one or more interface definitions";
  }
  extension extends {
    argument "target-component-identifier";
    description
      "used by a component to extend another component definition";
  }
  extension array {
    argument "array-name";
  }
  extension private {
    argument 'value';
    description
      "denote any arbitrary data node as being private (non-enumerable)";
  }
  /*
   * Dependencies
   */ 
  import ietf-yang-types {
    prefix yang;
  }
  /*
   * Features
   */
  feature viz {
    reference "visualization subsystem available.";
  }
  feature sim {
    reference "sumulation subsystem available.";
  }
  /*
   * Identities
   */
  identity transport {
    description "base identity for transport frames";
  }
  identity kson {
    base transport;
  }
  identity component {
    description "base identity for kinetic components";
  }
  /*
   * Type Definitions
   */
  typedef identifier {
    type yang:yang-identifier;
  }
  typedef unique-identifier {
    type yang:uuid;
  }
  typedef schema-identifier {
    type string; // need to qualify better
  }
  typedef node-identifier {
    type union {
      type uint32;
      type yang:uuid;
    }
  }
  typedef flow-identifier {
    type union {
      type uint32;
      type yang:uuid;
    }
  }
  typedef flow-mode {
    type enumeration {
      enum mesh;
      enum duplex;
      enum unicast;
    }
    default unicast;
  }
  /*
   * Structure Definitions
   */
  grouping element {
    leaf id {
      type kos:node-identifier;
      mandatory true;
    }
    anydata schema {
      mandatory true;
    }
    anydata instance {
      config false;
    }
  }
  grouping render {
    leaf name {
      type string;
    }
    leaf title {
      type string;
    }
    leaf color {
      type string;
    }
    leaf x {
      type uint16;
      default 0;
    }
    leaf y {
      type uint16;
      default 0;
    }
    leaf flip {
      type boolean;
      default false;
    }
  }
  grouping node {
    uses kos:element {
      refine schema {
        reference "kos:component";
      }
    }
    container render {
      uses kos:render;
    }
  }
  grouping flow {
    uses kos:element {
      refine schema {
        reference "grouping";
      }
    }
    leaf label {
      type string;
    }
    leaf mode {
      type kos:flow-mode;
    }
    leaf-list nodes {
      type kos:node-identifier;
      min-elements 2;
    }
    leaf-list frames {
      type identityref {
	base kos:transport;
      }
    }
    container control {
      leaf frequency {
	type uint32;
	units ms;
      }
    }
  }
  grouping error {
    leaf message {
      type string;
    }
    anydata origin;
  }
  /*
   * Operational state data nodes
   */
  container topology {
    description
      "Contains KOS network topology information.";
    leaf label {
      type string;
    }
    list node {
      key id;
      uses kos:node;
    }
    list flow {
      key id;
      uses kos:flow;
    }
  }
  notification error {
    uses kos:error;
  }
  notification log {
    leaf level;
    leaf message;
  }
}
