module kinetic-object-swarm {
  namespace "urn:ietf:params:xml:ns:yang:kinetic-object-swarm";
  prefix kos;

  organization
    "Corenova Technologies, Inc.";
  contact
    "Peter K. Lee <peter@corenova.com>";
  description
    "The core module of KOS which provides custom language extensions for
     modeling reactions and generators.";
  
  revision 2018-03-10 {
    description
      "Initial revision.";
  }
  /*
   * Custom YANG Language Extensions
   */
  extension processor {
    argument "processor-name";
  }
  extension reaction {
    argument "function-name";
  }
  extension topic {
    argument "topic-name";
  }
  extension flow {
    argument "target-topic-identifier";
  }
  extension node {
    argument "target-node-identifier";
  }
  extension filter {
    argument "filter-rule";
  }
  extension array {
    argument "array-name";
  }
  extension extends {
    argument "target-processor-identifier";
  }
  /*
   * Dependencies
   */ 
  import ietf-yang-types {
    prefix yang;
  }
  /*
   * Features
   */
  feature url {
    reference "nodejs://url";
  }
  feature net {
    reference "nodejs://net";
  }
  feature channel {
    reference "kos://channel";
  }
  feature interface {
    reference "kos://interface";
  }
  /*
   * Identities
   */
  identity protocol {
    description "base identity for protocols";
  }
  identity kos {
    base protocol;
  }
  identity nodejs {
    base protocol;
  }
  /*
   * Type Definitions
   */
  typedef identifier {
    type yang:yang-identifier;
  }
  typedef unique-identifier {
    type yang:uuid;
  }
  typedef topic {
    type string; // TODO: something better...
  }
  typedef reaction-identifier {
    description
      "A reference to a reaction node in the data model.";
    type instance-identifier {
      require-instance true;
    }
  }
  
  /*
   * Kinetic topics
   */
  grouping process {
    
  }
  grouping program {
    
  }
  grouping schema {
    
  }
  grouping persona {
    leaf id;
    leaf uri;
    leaf-list links;
  }
  grouping model {
    
  }
  grouping stream {
    // define Stream object schema
  }
  grouping state {
    
  }
  grouping debug {
    
  }
  grouping info {
    
  }
  grouping warn {
    
  }
  grouping log {
    
  }
  grouping error {
    leaf message {
      type string;
    }
    anydata origin;
  }
  grouping node-list {
    list node {
      
    }
  }
  grouping link-list {
    list link {
      
    }
  }
  grouping flow {
    leaf name {
      type kos:identifier;
    }
    leaf-list steps {
      type kos:reaction-identifier {
        require-instance true;
      }
    }
  }
  grouping flow-list {
    list flow {
      key id;
      leaf id {
        type kos:unique-identifier;
        mandatory true;
      }
      uses kos:flow;
    }
  }
  /*
   * Operational state data nodes
   */
  container topology {
    config false;
    description
      "Contains KOS network topology information.";
    uses node-list;
    uses link-list;
    uses flow-list;
  }
  notification error {
    leaf message;
    anydata origin;
  }
  notification log {
    leaf level;
    leaf message;
  }
}
