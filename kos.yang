module kinetic-open-storage {
  prefix kos;

  import node-package-manager { prefix npm; }
  
  feature client {
    if-feature npm:request;
  }
  feature server {
    if-feature npm:express;
  }

  extension query {
    
  }

  container store {
    
  }

  rpc join {
    
  }
  rpc bind {
    
  }
  rpc pull {
    
  }
  rpc push {
    
  }
  
}
