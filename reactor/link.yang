module kos-link {
  prefix link;

  import kinetic-object-swarm { prefix kos; }
  import kos-network   { prefix net; }
  import kos-websocket { prefix ws; }

  list session {
    key addr;
    leaf addr;
    anydata stream;
  }

  kos:forward "/net:connect";
  kos:forward "/ws:connect";
  
  kos:reaction connect {
    input {
      kos:pulse url {
        uses kos:resource;
      }
    }
    output {
      kos:pulse "/net:connect";
      kos:pulse "/ws:connect";
    }
  }
  
  
  kos:reaction streamify {
    input {
      kos:pulse "/net:connection";
    }
    output {
      kos:pulse "/link:session";
    }
  }
  
}
