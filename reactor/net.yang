module kos-network {
  prefix net;

  description
    "reactions to establish TCP/UDP client/server communication links";

  import kinetic-object-swarm { prefix kos; }

  feature nodejs-net;

  identity proto;
  identity tcp {
    base proto;
  }
  identity udp {
    base proto;
  }

  grouping url-object {
    leaf protocol {
      type identityref {
        base net:proto;
      }
      default tcp;
    }
    leaf hostname {
      type inet:ip-address;
      default "0.0.0.0";
    }
    leaf port {
      type uint16;
      default 12345;
    }
    leaf retry {
      type uint16;
      default 100;
    }
    leaf max {
      type uint16;
      default 5000;
    }
    leaf repair {
      type boolean;
      default false;
    }
  }

  list connection {
    leaf addr;
    anydata socket;
    anydata server;
    container opts;
  }
  
  rpc connect {
    if-feature nodejs-net;
    input {
      choice mode {
        case direct {
          uses url;
        }
        case indirect {
          if-feature nodejs-url;
          leaf url {
            type url;
          }
        }
      }
    }
  }
  
  kos:reaction connect {
    if-feature nodejs-net;
    input {
      
    }
    output {
      kos:pulse "/net:connection";
      kos:pulse "/net:socket";
    }
  }
}
