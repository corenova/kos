module kinetic-chrono {
  prefix chrono;

  description
    "system time reactors and reactions";
  
  import kinetic-object-stream {
    prefix kos;
  }
  typedef event-name {
    type kos:identifier;
  }
  grouping alarm {
    leaf name {
      type chrono:event-name;
    }
    leaf delay {
      type uint32 {
        range 0..360000; // maximum alarm delay is 1 hour
      }
      units ms;
      default 0;
    }
    leaf repeat {
      type boolean;
      default false;
    }
    leaf immediate {
      type boolean;
      default false;
    }
    leaf active {
      type boolean;
      default true;
    }
  }
  grouping alert {
    leaf name {
      type chrono:event-name;
    }
  }
  kos:reactor Timer {
    input {
      kos:data chrono:alarm;
    }
    output {
      kos:data chrono:alert;
    }
    list alarm {
      key "name";
      uses chrono:alarm;
      anydata timer;
    }
    kos:reaction schedule {
      input {
        kos:data chrono:alarm;
      }
      output {
        kos:data chrono:alert;
      }
    }
  }
}
