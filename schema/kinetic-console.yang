module kinetic-console {
  prefix console;

  import kinetic-object-stream {
    prefix kos;
  }
  import kinetic-render {
    prefix render;
  }

  feature colors {
    reference "npm://colors";
  }
  feature readline {
    reference "nodejs://readline";
  }
  
  grouping io {
    container input;
    container output;
    container source;
  }
  grouping prompt {
    
  }
  grouping line {
    leaf data {
      type string;
    }
  }
  kos:reaction initialize {
    input {
      kos:data kos:process;
      kos:data kos:program;
    }
    output {
      kos:data console:io;
    }
  }
  kos:reaction createConsole {
    if-feature console:readline;
    if-feature console:colors;
    input {
      kos:data kos:process {
        require-instance true;
      }
      kos:data console:io;
    }
    output {
      kos:data console:prompt;
      kos:data console:line;
    }
  }
  kos:reaction processInput {
    input {
      kos:data kos:process {
        require-instance true;
      }
      kos:data console:io;
      kos:data console:prompt;
    }
    output {
      kos:data render:info;
    }
  }
  kos:reaction renderReactor {
    input {
      kos:data kos:process {
        require-instance true;
      }
      kos:data kos:program {
        require-instance true;
      }
      //kos:data kos:reactor;
    }
    output {
      kos:data render:info;
    }
  }
}
