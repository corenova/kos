module kinetic-http {
  prefix http;
  description "interfaces to HTTP client/server requests";

  import kinetic-object-stream {
    prefix kos;
  }
  import kinetic-network {
    prefix net;
  }
  import ietf-inet-types {
    prefix inet;
  }
  /*
   * Features
   */
  feature express {
    reference "npm://express";
  }
  feature agent {
    reference "npm://superagent";
  }
  feature server {
    reference "nodejs://http";
  }
  /*
   * Identities
   */
  identity http {
    base net:tcp;
  }
  identity https {
    base net:ssl;
  }
  /*
   * Type Definitions
   */ 
  typedef content-type {
    type enumeration {
      enum "none";
      enum "form";
      enum "json";
      enum "xml";
      enum "file";
    }
    default "json";
  }
  
  /*
   * Groupings
   */
  grouping request {
    leaf url {
      type inet:uri;
      mandatory true;
    }
    leaf method {
      type enumeration {
        enum 'GET';
        enum 'POST';
        enum 'DELETE';
        enum 'POST';
        enum 'PUT';
        enum 'PATCH';
      }
    }
    leaf type {
      type http:content-type;
    }
    container header;
    leaf query {
      type string;
    }
    leaf timeout {
      type uint32;
      default 0;
      units ms;
    }
    anydata data;
  }
  grouping response {
    
  }
  grouping endpoint {
    uses net:endpoint {
      refine "protocol" {
        default "http";
      }
      refine "port" {
        default 80;
      }
    }
  }
  grouping server {
    
  }
  grouping server-request {
    
  }
  grouping route {
    
  }
  /*
   * Remote Procedure Calls
   */ 
  rpc request {
    if-feature http:agent;
    input {
      uses http:request;
    }
    output {
      uses http:response;
    }
  }
  /*
   * Kinetic Reactors
   */
  kos:reactor Connector {
    kos:reaction request {
      if-feature http:agent;
      input {
        kos:data http:request;
      }
      output {
        kos:data http:response;
      }
    }
  }
  kos:reactor Listener {
    kos:reaction listen {
      if-feature http:server;
      input {
        kos:data http:endpoint;
      }
      output {
        kos:data http:server;
        kos:data net:connection;
        kos:data http:server-request;
      }
    }
    kos:reaction route {
      input {
        kos:data http:server {
          require-instance true;
        }
        kos:data http:route;
      }
      output {
        kos:data http:server-request;
      }
    }
  }
}
