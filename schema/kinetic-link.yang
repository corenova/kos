module kinetic-link {
  prefix link;

  import kinetic-object-stream {
    prefix kos;
  }
  import kinetic-network {
    prefix net;
  }
  import kinetic-websocket {
    prefix ws;
  }
  feature parse {
    if-feature kos:json;
  }
  feature stringify {
    if-feature kos:json;
  }
  /*
   * Groupings
   */
  grouping endpoint {
    uses net:endpoint {
      refine "query/retry" {
        default true;
      }
    }
  }
  grouping channel {
    leaf uri {
      type net:uri;
    }
    anydata stream;
  }
  /*
   * Kinetic Reactors
   */
  kos:reactor Connector {
    kos:extends net:Connector;
    kos:extends ws:Connector;
    kos:extends link:Synchronizer;
  }
  kos:reactor Listener {
    kos:extends net:Listener;
    kos:extends ws:Listener;
    kos:extends link:Synchronizer;
  }
  kos:reactor Synchronizer {
    kos:reaction select {
      input {
        kos:data link:endpoint;
      }
      output {
        kos:data net:endpoint;
        kos:data ws:endpoint;
      }
    }
    kos:reaction sync {
      if-feature kos:channel;
      input {
        kos:data net:connection;
      }
      output {
        kos:data link:channel;
      }
    }
  }
}
