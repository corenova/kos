module kinetic-log {
  namespace "urn:ietf:params:xml:ns:yang:kos:kinetic-log";
  prefix log;
  description
    "reactions to KOS log events";

  import kinetic-object-stream { prefix kos; }
  import kinetic-console { prefix console; }

  container console;
}
