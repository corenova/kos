module kinetic-network {
  prefix net;
  
  import kinetic-object-stream {
    prefix kos;
  }
  import ietf-inet-types {
    prefix inet;
  }
  /*
   * Features
   */
  feature net {
    reference "nodejs://net";
  }
  feature socket {
    reference "nodejs://net?Socket";
  }
  feature server {
    reference "nodejs://net?Server";
  }
  /*
   * Identities
   */
  identity ethernet {
    base kos:transport;
  }
  identity ip {
    base net:ethernet;
  }
  identity tcp {
    base net:ip;
  }
  identity udp {
    base net:ip;
  }
  identity unix {
    base kos:transport;
  }
  identity ssl {
    base net:tcp;
  }
  /*
   * Type Definitions
   */
  typedef uri {
    type inet:uri;
  }
  typedef connection-ref {
    type leafref {
      path "/net:session/connection/uri";
    }
  }
  /*
   * Groupings
   */
  grouping persist-options {
    leaf timeout {
      type uint16;
      default 0;
      units 'ms';
    }
    leaf retry {
      type union {
        type boolean;
        type uint16;
      }
      default false;
    }
    leaf max {
      type uint16;
      units 'ms';
      default 5000;
    }
  }
  grouping endpoint {
    leaf protocol {
      type identityref {
        base kos:transport;
      }
      default "tcp";
    }
    leaf hostname {
      type inet:host;
      default '0.0.0.0';
    }
    leaf port {
      type inet:port-number;
      default 12345;
    }
    leaf pathname {
      type string;
    }
    leaf slashes {
      kos:private true;
      type boolean;
      default true;
    }
    container query {
      uses persist-options;
    }
    anydata socket {
      if-feature net:socket;
      kos:private true;
    }
    // below placed last for a reason...
    leaf uri {
      if-feature kos:url;
      type net:uri;
    }
  }
  grouping request {
    uses net:endpoint {
      augment "query" {
        leaf single {
          type boolean;
          default true;
          description
            "denote that the request will end connection after a single transaction";
        }
      }
    }
    anydata data;
  }
  grouping response {
    uses net:endpoint;
    anydata data;
  }
  grouping connection {
    leaf uri {
      type net:uri;
      mandatory true;
    }
    leaf server {
      if-feature net:server;
      type union {
        type leafref {
          path "/net:topology/local/uri";
        }
        type net:uri;
      }
    }
    anydata socket {
      kos:private true;
      //config false;
    }
    anydata stream {
      if-feature kos:stream;
      kos:private true;
      //config false;
    }
  }
  grouping server {
    
  }
  /*
   * Module Configuration and State
   */
  container topology {
    config false;
    list remote {
      key uri;
      uses net:endpoint;
      leaf active {
        config false;
        type boolean;
        default false;
      }
      max-elements 255;
    }
    list local {
      key uri;
      uses net:endpoint;
      leaf active {
        config false;
        type boolean;
        default false;
      }
      leaf-list connections {
        config false;
        type net:connection-ref;
      }
      max-elements 10;
    }
  }
  container session {
    config false;
    list connection {
      key uri;
      uses net:connection;
    }
  }
  rpc connect {
    if-feature net:socket;
    input {
      uses net:endpoint;
    }
    output {
      anydata socket {
        kos:private true;
      }
    }
  }
  /*
   * Kinetic Interfaces
   */
  kos:interface Connector {
    kos:reaction connect {
      if-feature net:socket;
      input {
        kos:data net:endpoint;
      }
      output {
        kos:data net:connection;
        kos:data net:endpoint;
      }
    }
    kos:reaction request {
      if-feature net:net;
      input {
        kos:data net:request;
      }
      output {
        kos:data net:response;
      }
    }
  }
  kos:interface Listener {
    kos:reaction listen {
      if-feature net:server;
      input {
        kos:data net:endpoint;
      }
      output {
        kos:data net:connection;
        kos:data net:server;
        kos:node "/net:topology/local";
      }
    }
  }
}
