module kinetic-react-js {
  namespace "urn:ietf:params:xml:ns:yang:kinetic-react-js";
  prefix react;

  organization
    "Corenova Technologies, Inc.";
  contact
    "Peter K. Lee <peter@corenova.com>";
  description
    "A module that encapsulates React.js related data models and provides
     KOS generators for working with React Components.";
  
  import kinetic-object-stream {
    prefix kos;
  }
  /*
   * Features
   */
  feature dom {
    reference "npm://react-dom";
  }
  feature router {
    reference "npm://react-router";
  }
  typedef lifecycle {
    type enumeration {
      enum mounting;
      enum mounted;
      enum unmounting;
      enum updating;
      enum updated;
      enum receive;
    }
  }
  /*
   * Groupings
   */
  grouping component {
    container kos;
    // action setState;
    // action componentWillMount;
    // action componentDidMount;
    // action componentWillUnmount;
    // action componentDidUpdate;
    // action componentWillReceiveProps;
  }
  grouping setter;
  grouping lifecycle {
    leaf active {
      type boolean;
      default false;
    }
    leaf state {
      type react:lifecycle;
    }
    leaf-list args;
  }
  grouping props;
  grouping state;
  grouping event;
  grouping trigger {
    leaf topic {
      type kos:topic;
    }
    anydata data;
  }
  grouping form-clear;
  grouping route {
    leaf to {
      type string;
    }
  }
  /*
   * Kinetic Reactors
   */
  kos:reactor Component {
    description
      "An interface that consumes React.Component instances and captures
       lifecycle events and state changes";
    /*
     * Kinetic Reactions
     */
    kos:reaction transform {
      input {
        kos:data react:component;
      }
      output {
        kos:data react:lifecycle;
        kos:data react:setter;
        kos:data react:event;
        kos:data react:trigger;
        kos:data react:props;
        kos:data react:state;
      }
    }
    kos:reaction route {
      input {
        kos:data react:props {
	  require-instance true;
	}
	kos:data react:route;
      }
    }
    kos:reaction applyState {
      input {
        kos:data react:lifecycle {
          require-instance true;
        }
        kos:data react:setter {
          require-instance true;
        }
        kos:data react:state;
      }
    }
  }
  kos:reactor Form {
    kos:extends react:Component;

    description
      "An interface that extends React.Component instances and handles
       form related activity (i.e. onClick, onChange) and automates
       state updates related to form data.";
    
    kos:reaction saveFormData {
      input {
        kos:data react:event;
      }
      output {
        kos:data react:state; // FUTURE
      }
    }
    kos:reaction clearForm {
      if-feature react:dom;
      input {
        kos:data react:component {
          require-instance true;
        }
        kos:data react:form-clear;
      }
    }
  }
}
