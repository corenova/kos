module kinetic-render {
  namespace "urn:ietf:params:xml:ns:yang:kos:kinetic-render";
  prefix render;
  description
    "reactions to visually render reactors";

  feature theme{
    
  }
  feature treeify {
    reference "npm://treeify";
  }
  
  import kinetic-object-stream {
    prefix kos;
  }

  grouping info {
    container source;
    container output;
  }
  grouping output {
    
  }
  grouping reactor {
    
  }
  grouping reactor-tree {
    
  }

  container theme {
    grouping tree-item {
      leaf top;
      leaf item;
      leaf last;
      leaf mid1;
      leaf mid2;
      leaf mid3;
      leaf one;
      leaf dash;
    }
    container BOX {
      container L {
        uses tree-item;
      }
      container R {
        uses tree-item;
      }
      leaf nest;
      leaf item;
      leaf last;
    }
    leaf FUNC;
    leaf SEP;
  }

  kos:reaction renderInfo {
    input {
      kos:data render:info;
    }
    output {
      kos:data render:reactor;
      kos:data render:output;
    }
  }
  kos:reaction renderModelAsTree {
    if-feature render:theme;
    if-feature render:treeify;
    input {
      kos:data render:reactor;
    }
    output {
      kos:data render:reactor-tree;
    }
  }
  kos:reaction outputModelTree {
    input {
      kos:data render:output {
        require-instance true;
      }
      kos:data render:reactor-tree;
    }
    output {
      // no output...
    }
  }

}
