module kinetic-websocket {
  namespace "urn:ietf:params:xml:ns:yang:kinetic-websocket";
  prefix ws;

  organization
    "Corenova Technologies, Inc.";
  contact
    "Peter K. Lee <peter@corenova.com>";

  import kinetic-object-stream {
    prefix kos;
  }
  import kinetic-network {
    prefix net;
  }
  /*
   * Features
   */
  feature socket {
    reference "npm://simple-websocket";
  }
  feature server {
    reference "npm://simple-websocket/server";
  }
  /*
   * Identities
   */
  identity ws {
    base net:tcp;
  }
  identity wss {
    base net:tcp;
  }
  /*
   * Groupings
   */
  grouping endpoint {
    uses net:endpoint {
      refine protocol {
        default "ws";
        must ". = 'ws' or . = 'wss'" {
          error-message "A websocket protocol must be 'ws' or 'wss'";
        }
      }
      refine port {
        default 80;
      }
    }
  }
  grouping server {
    
  }
  /*
   * Kinetic Reactors
   */
  kos:reactor Connector {
    kos:reaction connect {
      if-feature ws:socket;
      input {
        kos:data ws:endpoint;
      }
      output {
        kos:data ws:endpoint;
        kos:data net:connection;
      }
    }
  }
  kos:reactor Listener {
    kos:reaction listen {
      if-feature ws:server;
      input {
        kos:data ws:endpoint;
      }
      output {
        kos:data ws:server;
        kos:data net:connection;
      }
    }
  }
}
