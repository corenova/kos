module kinetic-network {
  prefix net;
  
  import kinetic-object-swarm {
    prefix kos;
  }
  import ietf-inet-types {
    prefix inet;
  }
  /*
   * Features
   */
  feature socket {
    reference "nodejs://net?Socket";
  }
  feature server {
    reference "nodejs://net?Server";
  }
  /*
   * Identities
   */
  identity tcp {
    base kos:protocol;
  }
  identity udp {
    base kos:protocol;
  }
  identity unix {
    base kos:protocol;
  }
  /*
   * Type Definitions
   */ 
  typedef connection-ref {
    type leafref {
      path "/net:session/connection/uri";
    }
  }
  /*
   * Groupings
   */
  grouping persist-options {
    leaf retry {
      type union {
        type boolean;
        type uint16;
      }
      default false;
    }
    leaf max {
      type uint16;
      units 'ms';
      default 5000;
    }
    leaf repair {
      type boolean;
      default false;
    }
  }
  grouping endpoint {
    uses kos:endpoint {
      refine "protocol" {
        default "tcp";
        must ". = 'tcp' or . = 'udp' or . = 'unix'" {
          error-message "A net protocol must be 'tcp' or 'udp' or 'unix'";
        }
      }
      refine "port" {
        default 12345;
      }
      augment "query" {
        uses persist-options;
      }
    }
  }
  grouping remote {
    uses net:endpoint;
    anydata socket {
      if-feature net:socket;
    }
  }
  grouping local {
    uses net:endpoint;
    anydata server {
      if-feature net:server;
    }
  }
  grouping connection {
    leaf uri {
      type inet:uri;
      mandatory true;
    }
    leaf server {
      if-feature net:server;
      type leafref {
        path "/net:topology/local/uri";
      }
    }
    anydata socket {
      if-feature net:socket;
      config false;
    }
    anydata stream {
      if-feature kos:stream;
      config false;
    }
  }
  /*
   * Module Configuration and State
   */
  container topology {
    config false;
    list remote {
      key uri;
      uses net:remote;
      leaf active {
        config false;
        type boolean;
        default false;
      }
      max-elements 255;
    }
    list local {
      key uri;
      uses net:local;
      leaf active {
        config false;
        type boolean;
        default false;
      }
      leaf-list connections {
        config false;
        type net:connection-ref;
      }
      max-elements 10;
    }
  }
  container session {
    config false;
    list connection {
      key uri;
      uses net:connection;
    }
  }
  /*
   * Kinetic Reactions
   */
  kos:reaction connect {
    if-feature net:socket;
    input {
      kos:flow net:remote;
    }
    output {
      kos:flow net:connection;
      kos:flow net:remote;
    }
  }
  kos:reaction listen {
    if-feature net:server;
    input {
      kos:flow net:local;
    }
    output {
      kos:flow net:connection;
      kos:flow net:server;
    }
  }
  kos:reaction streamify {
    input {
      kos:flow net:connection;
    }
    output {
      kos:flow kos:stream;
    }
  }
}
