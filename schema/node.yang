module kinetic-node-js {
  prefix nodejs;

  description
    "reactions to Node.js runtime environment interactions";
  
  import kinetic-object-swarm {
    prefix kos;
  }
  /*
   * System Features
   */
  feature fs;
  feature url;
  feature net;
  feature path;
  
  /*
   * Pulse definitions
   */
  grouping process {
    
  }
  grouping program {
    
  }
  grouping module {
    
  }
  grouping require {
    
  }
  grouping resolve {
    
  }
  grouping load {
    
  }
  grouping read {
    
  }
  grouping log {
    
  }

  container foo {
    leaf bar;
  }
  
  kos:reaction initialize {
    input {
      kos:data nodejs:process;
    }
    output {
      kos:data nodejs:resolve;
    }
  }
  kos:reaction execute {
    input {
      kos:data nodejs:program;
    }
    output {
      kos:data nodejs:load;
      kos:data nodejs:read;
      kos:data nodejs:log;
    }
  }
  kos:reaction load {
    if-feature nodejs:path;
    input {
      kos:data nodejs:load;
    }
    output {
      kos:data kos:schema;
      kos:data nodejs:resolve;
    }
  }
  kos:reaction resolve {
    input {
      kos:data nodejs:resolve;
    }
    output {
      kos:data nodejs:require;
    }
  }
  kos:reaction require {
    input {
      kos:data nodejs:require;
    }
    output {
      kos:data nodejs:module;
    }
  }
  kos:reaction read {
    if-feature nodejs:fs;
    input {
      kos:data nodejs:read;
    }
    output {
        
    }
  }
}
