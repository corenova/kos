module kinetic-react-js {
  prefix react;
  yang-version "1.1";

  import kinetic-object-swarm {
    prefix kos;
  }
  /*
   * Groupings
   */
  grouping event {
    reference "React.js SyntheticEvent";
  }
  grouping select-action {
    action select {
      input {
        uses react:event;
      }
    }
    notification selected;
  }
  

  grouping component {
    container props;
    container state;

    action setState;
    action componentWillMount;
    action componentDidMount;
    action componentWillUpdate;
    action componentDidUpdate;
    action componentWillReceiveProps;
    
    notification mounting;
    notification mounted;
    notification updating;
    notification updated;
    notification receiving;
  }
  
  kos:reaction wrap {
    input {
      kos:data react:component;
    }
    output {
      kos:data react:setter;
      kos:data react:mounting;
      kos:data react:mounted;
      kos:data react:updating;
      kos:data react:updated;
      kos:data react:receive;
      kos:data react:event;
      kos:data react:state;
    }
  }
  kos:reaction mount {
    input {
      kos:data react:mounting;
    }
    output {
      kos:data kos:persona;
    }
  }
}
