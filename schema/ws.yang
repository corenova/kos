module kinetic-websocket {
  prefix ws;
  
  import kinetic-object-swarm {
    prefix kos;
  }
  import kinetic-network {
    prefix net;
  }
  import ietf-inet-types {
    prefix inet;
  }
  /*
   * Features
   */
  feature socket {
    reference "npm://simple-websocket";
  }
  feature server {
    if-feature ws:socket;
    reference "npm://simple-websocket/server";
  }
  /*
   * Identities
   */
  identity ws {
    base net:tcp;
  }
  identity wss {
    base net:tcp;
  }
  /*
   * Groupings
   */
  grouping remote {
    uses net:remote {
      refine "protocol" {
        default "ws";
        must ". = 'ws' or . = 'wss'" {
          error-message "A websocket protocol must be 'ws' or 'wss'";
        }
      }
      refine "port" {
        default 80;
      }
    }
  }
  grouping local {
    uses net:remote {
      refine "protocol" {
        default "ws";
        must ". = 'ws' or . = 'wss'" {
          error-message "A websocket protocol must be 'ws' or 'wss'";
        }
      }
      refine "port" {
        default 80;
      }
    }
  }
  /*
   * Kinetic Reactions
   */
  kos:reaction connect {
    if-feature ws:socket;
    input {
      kos:flow ws:remote;
    }
    output {
      kos:flow net:connection;
      kos:flow ws:remote;
    }
  }
  kos:reaction listen {
    if-feature ws:server;
    input {
      kos:flow ws:local;
    }
    output {
      kos:flow net:server;
    }
  }
}
