module kinetic-link {
  prefix link;

  import kinetic-object-stream {
    prefix kos;
  }
  import kinetic-network {
    prefix net;
  }
  import kinetic-websocket {
    prefix ws;
  }
  feature parse {
    if-feature kos:json;
  }
  feature stringify {
    if-feature kos:json;
  }
  /*
   * Groupings
   */
  grouping endpoint {
    uses net:endpoint {
      refine "query/retry" {
        default true;
      }
    }
  }
  grouping session {
    leaf uri {
      type net:uri;
    }
    anydata stream;
  }
  /*
   * Kinetic Interfaces
   */
  kos:interface Connector {
    kos:extends net:Connector;
    kos:extends ws:Connector;
    kos:extends link:Synchronizer;
  }
  kos:interface Listener {
    kos:extends net:Listener;
    kos:extends ws:Listener;
    kos:extends link:Synchronizer;
  }
  kos:interface Synchronizer {
    kos:reaction select {
      input {
        kos:data link:endpoint;
      }
      output {
        kos:data net:endpoint;
        kos:data ws:endpoint;
      }
    }
    kos:reaction sync {
      if-feature kos:channel;
      input {
        kos:data net:connection;
      }
      output {
        kos:data link:session;
      }
    }
  }
}
